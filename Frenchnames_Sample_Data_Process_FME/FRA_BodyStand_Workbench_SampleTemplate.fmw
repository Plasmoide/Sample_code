FME workspace FRA_BodyStand_Workbench_SampleTemplate.fmw

Parameters:
- SourceDataset_CSV2 = $(FME_MF_DIR)FRA_StreetNameClassifier_Standardization.csv   # Source CSV (Comma Separated Value) File(s)
- DestDataset_CSV2 = $(FME_MF_DIR)FME_out   # Destination CSV (Comma Separated Value) Folder
- DestDataset_CSV2_6 = $(FME_MF_DIR)FME_out   # Destination CSV (Comma Separated Value) Folder
- DestDataset_CSV2_5 = $(FME_MF_DIR)FME_out   # Destination CSV (Comma Separated Value) Folder

Readers:
- CSV2_1: CSV2 from $(SourceDataset_CSV2)

Writers:
- CSV2_2: CSV2 to $(DestDataset_CSV2)
- CSV2_3: CSV2 to $(DestDataset_CSV2_6)
- CSV2_4: CSV2 to $(DestDataset_CSV2_5)

AttributeCreator_6
    ATTR_TABLE = SET_TO unsupported_lang = FME_CONDITIONAL:DEFAULT_VALUE'_FME_NO_OP_'BOOL_OP;OR;COMPOSITE_TEST;1;CASE_SENSITIVE_TEST @Value(language_code) CONTAINS_REGEX ^br|gsw|co|nl|und'true'FME_NUM_CONDITIONS2___
    -> Tester_4
Tester_4
    BOOL_OP = OR
    COMPOSITE_TEST = 1
    TEST_CLAUSE = TEST @Value(unsupported_lang) = true
    TEST_MODE = TEST
    PASSED -> AttributeValueMapper_2
    FAILED -> FRA_OtherNamingClassifier_Standardization (writer CSV2_4)
AttributeValueMapper_2
    DIRECTION = Forward (Source To Destination)
    LUT = und,undetermined_Classifier,nl,dutch_Classifier
    SRC = language_code
    VAL_ATTR = sub_type
    -> AttributeCreator
FRA_OtherNamingClassifier_Standardization (writer CSV2_4)
    attributes: id uint8, language_code string, script_code string, country_code string, full_token string, english_translation string, standard_abbreviation string, additional_abbreviations string, prefix_form string, suffix_form string, is_prefix_abbreviation string, is_suffix_abbreviation string, enum_value string, compound_classifier string, invalid_body_token string, classifier_type string, can_attach_body string, gender string, source string
UniqueValueLogger_3
    VAL = @Value(language_code)
AttributeCreator_3
    ATTR_TABLE = SET_TO unsupported_lang = FME_CONDITIONAL:DEFAULT_VALUE'_FME_NO_OP_'BOOL_OP;OR;COMPOSITE_TEST;1;CASE_SENSITIVE_TEST @Value(language_code) CONTAINS_REGEX ^br|gsw|co|nl|und'true'FME_NUM_CONDITIONS2___
    -> Tester
Tester
    BOOL_OP = OR
    COMPOSITE_TEST = 1
    TEST_CLAUSE = TEST @Value(unsupported_lang) = true
    TEST_MODE = TEST
    PASSED -> AttributeValueMapper_4
    FAILED -> FRA_StreetNameClassifier_Standardization (writer CSV2_3)
AttributeValueMapper_4
    DIRECTION = Forward (Source To Destination)
    LUT = und,undetermined_Classifier,nl,dutch_Classifier
    SRC = language_code
    VAL_ATTR = sub_type
    -> AttributeCreator
FRA_StreetNameClassifier_Standardization (writer CSV2_3)
    attributes: id uint16, language_code string, script_code string, country_code string, full_token string, standard_abbreviation string, additional_abbreviations string, gender string, english_translation string, standard_form string, prefix_form string, suffix_form string, is_prefix_abbreviation string, is_suffix_abbreviation string, compound_classifier string, invalid_body_token string, can_attach_body string, attach_position string, phoneme_lhplus string, phoneme_xsampa string, source string
UniqueValueLogger
    VAL = @Value(language_code)
Note: Input list of unsupported languages here.
AttributeCreator_5
    ATTR_TABLE = SET_TO unsupported_lang = FME_CONDITIONAL:DEFAULT_VALUE'_FME_NO_OP_'BOOL_OP;OR;COMPOSITE_TEST;1;CASE_SENSITIVE_TEST @Value(language_code) CONTAINS_REGEX ^br|gsw|co|nl|und'true'FME_NUM_CONDITIONS2___
    -> Tester_3
Note: Separating unsupported and supported languages for processing/upload. / - Make sure to put failed values into a writer thats a copy of the reader.
Tester_3
    BOOL_OP = OR
    COMPOSITE_TEST = 1
    TEST_CLAUSE = TEST @Value(unsupported_lang) = true
    TEST_MODE = TEST
    PASSED -> AttributeValueMapper
    FAILED -> FRA_Honorific_Standardization (writer CSV2_4)
Note: - Create Writers for each Reader we have put in and select "Copy from reader" option so it will have the same columns. / - The unsupported languages will continue on through the process and be converted to Body_Standardization. / - The rest will go back into the writers and be used to update Github.
Note: Rename them as their sub_type for each language. Language name should be lowercase. You can easily add new languages in by clicking an empty cell. / - the languages in here should match unsupported_lang / - their sub_type should match where they came from. Ex: french_Honorific, french_Particle, etc.
AttributeValueMapper
    DIRECTION = Forward (Source To Destination)
    LUT = und,undetermined_Classifier,nl,dutch_Classifier
    SRC = language_code
    VAL_ATTR = sub_type
    -> AttributeCreator
FRA_Honorific_Standardization (writer CSV2_4)
    attributes: id uint8, language_code string, script_code string, country_code string, full_token string, standard_abbreviation string, additional_abbrev string, standard_form string, prefix_form string, suffix_form string, gender string, capitalization_rule string, compound_honorific string, source string
Note: This will tell you what different languages are in each table. / - We have to separate supported and unsupported languages in the next step. / - Double check to make sure that Frances provided you with this a list. / - The output for UniqueValueLogger should not be connected to anything else.
UniqueValueLogger_4
    VAL = @Value(language_code)
AttributeCreator_4
    ATTR_TABLE = SET_TO unsupported_lang = FME_CONDITIONAL:DEFAULT_VALUE'_FME_NO_OP_'BOOL_OP;OR;COMPOSITE_TEST;1;CASE_SENSITIVE_TEST @Value(language_code) CONTAINS_REGEX ^br|gsw|co|nl|und'true'FME_NUM_CONDITIONS2___
    -> Tester_2
Tester_2
    BOOL_OP = OR
    COMPOSITE_TEST = 1
    TEST_CLAUSE = TEST @Value(unsupported_lang) = true
    TEST_MODE = TEST
    PASSED -> AttributeValueMapper_3
    FAILED -> FRA_Particle_Standardization (writer CSV2_4)
AttributeValueMapper_3
    DIRECTION = Forward (Source To Destination)
    LUT = und,undetermined_Classifier,nl,dutch_Classifier
    SRC = language_code
    VAL_ATTR = sub_type
    -> AttributeCreator
Note: Starting to create fields that will go into Body_Standardization output table. / -body_lang_code: should be the main language for the country you are working on.
AttributeCreator
    ATTR_TABLE:
      SET_TO body_lang_code = fr
      SET_TO body_country_code = @Value(country_code)
      SET_TO origin_lang_code = @Value(language_code)
      SET_TO body_script_code = @Value(script_code)
      SET_TO new_extraction = true
    -> AttributeCreator_2
Note: Creating columns that will go into Body_Standardization output but requires conditionals. / -display_form = standard_form. Particles does not have standard form so it is fulltoken. / -name_position = prefix/suffix, which position does it fall in usually. Particles does not have prefix/suffix so it should be empty in this field (check to see that it is).
AttributeCreator_2
    ATTR_TABLE:
      SET_TO display_form = FME_CONDITIONAL:DEFAULT_VALUE'@Value(full_token)'BOOL_OP;AND;COMPOSITE_TEST;1 AND 2 AND 3;TEST standard_form ATTRIBUTE_IS_MISSING _FME_BLANK_STRING_;TEST prefix_form ATTRIBUTE_IS_MISSING _FME_BLANK_STRING_;TEST suffix_form ATTRIBUTE_IS_MISSING _FME_BLANK_STRING_'@Value(full_token)'BOOL_OP;AND;COMPOSITE_TEST;1;TEST standard_form ATTRIBUTE_HAS_A_VALUE _FME_BLANK_STRING_'@Value(standard_form)'BOOL_OP;OR;COMPOSITE_TEST;1;TEST @Value(prefix_form) = @Value(suffix_form)'@Value(prefix_form)'BOOL_OP;OR;COMPOSITE_TEST;1;TEST @Value(prefix_form) = -'@Value(suffix_form)'BOOL_OP;OR;COMPOSITE_TEST;1;TEST @Value(suffix_form) = -'@Value(prefix_form)'FME_NUM_CONDITIONS6___
      SET_TO name_position = FME_CONDITIONAL:DEFAULT_VALUE'_FME_NO_OP_'BOOL_OP;AND;COMPOSITE_TEST;1 AND 2;TEST prefix_form ATTRIBUTE_IS_MISSING _FME_BLANK_STRING_;TEST suffix_form ATTRIBUTE_IS_MISSING _FME_BLANK_STRING_''BOOL_OP;OR;COMPOSITE_TEST;1;TEST @Value(prefix_form) != -'prefix'BOOL_OP;OR;COMPOSITE_TEST;1;TEST @Value(suffix_form) != -'suffix'BOOL_OP;OR;COMPOSITE_TEST;1;TEST @Value(prefix_form) = @Value(suffix_form)'prefix'BOOL_OP;OR;COMPOSITE_TEST;1;TEST @Value(prefix_form) = -'suffix'BOOL_OP;OR;COMPOSITE_TEST;1;TEST @Value(suffix_form) = -'prefix'FME_NUM_CONDITIONS7___
      SET_TO capitalization_rule = FME_CONDITIONAL:DEFAULT_VALUE'sentence_case'BOOL_OP;OR;COMPOSITE_TEST;1;TEST capitalization_rule ATTRIBUTE_HAS_A_VALUE _FME_BLANK_STRING_'@Value(capitalization_rule)'FME_NUM_CONDITIONS2___
    -> Sorter_Alphabet
Note: Sort values alphabetically first by sub_type so that languages are together, then by full_token.
Sorter_Alphabet
    SORT_PARM = sub_type ALPHA ASCENDING full_token ALPHA ASCENDING
    SORTED -> Counter_id
Note: Gives values new id numbers from how they were last sorted.
Note: Output columns should include: drop everything else. / - id / - sub_type / - body_lang_code / - body_country_code / - origin_lang_code / - body_script_code / - full_token / - standard_abbreviation / - additional_abbreviation / - gender / - display_form / - name_position / - capitalization_rule / - source / Make sure these only contains the languages that are unsupported. Ask Frances if you are unsure.
Counter_id
    CNT_ATTR = id
    DOMAIN = counter
    SCOPE = Local
    START = 80
    -> FRA_Body_StandardizationFME (writer CSV2_2)
FRA_Particle_Standardization (writer CSV2_4)
    attributes: id uint8, language_code string, script_code string, country_code string, full_token string, gender string, capitalization_rule string, source string
UniqueValueLogger_2
    VAL = @Value(language_code)

Bookmark: Git_OtherNamingClassifier
FRA_OtherNamingClassifier_Standardization (reader CSV2_1)
    attributes: id uint8, language_code string, script_code string, country_code string, full_token string, english_translation string, standard_abbreviation string, additional_abbreviations string, prefix_form string, suffix_form string, is_prefix_abbreviation string, is_suffix_abbreviation string, enum_value string, compound_classifier string, invalid_body_token string, classifier_type string, can_attach_body string, gender string, source string
    -> UniqueValueLogger_3
    -> AttributeCreator_6

Bookmark: Git_StreetNameClassifier_Standardization
FRA_StreetNameClassifier_Standardization (reader CSV2_1)
    attributes: id uint16, language_code string, script_code string, country_code string, full_token string, standard_abbreviation string, additional_abbreviations string, gender string, english_translation string, standard_form string, prefix_form string, suffix_form string, is_prefix_abbreviation string, is_suffix_abbreviation string, compound_classifier string, invalid_body_token string, can_attach_body string, attach_position string, phoneme_lhplus string, phoneme_xsampa string, source string
    -> UniqueValueLogger
    -> AttributeCreator_3

Bookmark: Git_Honorific
FRA_Honorific_Standardization (reader CSV2_1)
    attributes: id uint8, language_code string, script_code string, country_code string, full_token string, standard_abbreviation string, additional_abbrev string, standard_form string, prefix_form string, suffix_form string, gender string, capitalization_rule string, compound_honorific string, source string
    -> UniqueValueLogger_4
    -> AttributeCreator_5

Bookmark: Git_Particle
FRA_Particle_Standardization (reader CSV2_1)
    attributes: id uint8, language_code string, script_code string, country_code string, full_token string, gender string, capitalization_rule string, source string
    -> UniqueValueLogger_2
    -> AttributeCreator_4

Bookmark: Body_Standardization Output
FRA_Body_StandardizationFME (writer CSV2_2)
    attributes: id uint8, sub_type string, body_lang_code string, body_country_code string, origin_lang_code string, body_script_code string, full_token string, standard_abbreviation string, additional_abbreviations string, gender string, display_form string, name_position string, capitalization_rule string, source string

FME custom transformer UniqueValueLogger
Description
This transformer lists all of the unique values for a chosen attribute alongside  a count attribute of the number of occurrences of each of these values. The information is logged in both the Translation Window / Workspace log file, and stored in attributes.
This transformer is useful when you are creating a workspace and need to know the possible values to use in a filter.
Input Ports
Input: This transformer accepts any features with an attribute.
Output Ports
Output: Features are output with the attribute selected as the unique value to filter, and a new attribute containing the number of occurrences of each unique value. All other attributes are removed. 
_count: Number of occurrences of each unique value.
_value: Unique values of selected attribute.
Parameters
Attribute to Analyze: Select the attribute for the transformer to run analysis on. 
Notes
Transformer alternatives:
Duplicate Filter - Consider using this transformer if you are looking to get a list of unique values and do not need a _count attribute 
StatisticsCalculator - Setting the Group By mode to the attribute to analyze will produce the same result as this transformer, it may beuse If you would like to gather other statistics as well as count of the unique attributes.

Parameters:
- VAL =   # Attribute to Analyze

Input (input)
    -> AttributeCreator

Bookmark: Count unique attribute values
AttributeCreator
    ATTR_TABLE = SET_TO _value = $(VAL)
    -> AttributeKeeper
Note: Remove unwanted / attributes
AttributeKeeper
    KEEP_ATTRS = _value
    -> Aggregator
Note: Create aggregates of / features, grouped by / the target attribute value
Aggregator
    ACCUM_ATTRS_NAME = Merge Incoming Attributes
    AGGREGATE_TYPE = Homogeneous Collection (If Possible)
    COUNT_ATTR = _count
    GROUP_BY = _value
    MODE = Geometry - Assemble One Level
    SEP = ,
    AGGREGATE -> StringConcatenator
Note: Concatenate unique values / with their occurrence counts
StringConcatenator
    ACTION = Create New Attribute
    PARM_LINE = fme_basicstring:14%1%14%1:@Value(_value),@Value(_count)
    VAL_ATTR = _concatenated
    -> Sorter
Note: Sort output based on / occurrence count and / attribute value
Sorter
    SORT_PARM = _count NUMERIC DESCENDING _value ALPHA ASCENDING
    SORTED -> ListBuilder
    SORTED -> AttributeManager

Bookmark: Create output
AttributeManager
    ATTR_TABLE = REMOVE _concatenated
    -> Output (output)
Output (output)

Bookmark: Log unique attribute values
Note: Turn all input features / Into a single list
ListBuilder
    LIST_NAME = _list
    -> ListConcatenator
Note: Concatenate values of / the list into an attribute
ListConcatenator
    DROP_EMPTY_PARTS = No
    LIST_ATTR = _list{}._concatenated
    VAL_ATTR = UNIQUE VALUES
    -> StringConcatenator_2
Note: Add header
StringConcatenator_2
    ACTION = Create New Attribute
    PARM_LINE = "\n\nVALUE, COUNT\n@Value(UNIQUE VALUES)\n"
    VAL_ATTR = UNIQUE VALUES
    -> AttributeRemover_2
Note: Remote the list
AttributeRemover_2
    LIST_ATTRS = _list{}
    -> Logger
Note: Log the single feature / that contains the / output attribute
Logger
    LOG_FEATURE = LOG_RECORD
    MAXCOORDS = 1
    MAXFEATS = 1
    MESSAGE = Unique values:
    SEVERITY = INFO
